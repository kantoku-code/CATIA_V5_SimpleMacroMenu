Attribute VB_Name = "Button_Evt"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'vba CATIA V5用　ﾏｸﾛ起動(ﾃﾇｷ)ﾒﾆｭｰ  by Kantoku
'Button_Evt.cls
'ﾎﾞﾀﾝのｸﾘkｯｸｲﾍﾞﾝﾄを保持しています

Option Explicit
Private WithEvents mBtn As MSForms.CommandButton
Attribute mBtn.VB_VarHelpID = -1
Private mInfo As Object
Private mParentForm As MSForms.UserForm
Private mCloseType As Boolean

'Cat_Macro_Menu_Model.bas
'と一致させて欲しい(ｽｺｰﾌﾟ大きくしたくない)
Private Const TAG_ENTRYPNT = "ep"           'ﾀｸﾞｴﾝﾄﾘｰﾎﾟｲﾝﾄ
Private Const TAG_PJTPATH = "pjt_path"      'ﾀｸﾞﾌﾟﾛｼﾞｪｸﾄﾊﾟｽ
Private Const TAG_MDLNAME = "mdl_name"      'ﾀｸﾞﾓｼﾞｭｰﾙ名

'設定
Sub set_Event(ByVal Btn As MSForms.CommandButton, _
              ByVal BtnInfo As Object, _
              ByVal ParentForm As MSForms.UserForm, _
              ByVal CloseType As Boolean)
    Set mBtn = Btn
    Set mInfo = BtnInfo
    Set mParentForm = ParentForm
    mCloseType = CloseType
End Sub

'ﾎﾞﾀﾝｸﾘｯｸｲﾍﾞﾝﾄ
Private Sub mBtn_Click()
    If Not mCloseType Then Unload mParentForm
    
    Dim ary: ary = Array()
    Dim ss: Set ss = CATIA.SystemService
    
    Call ss.ExecuteScript(mInfo(TAG_PJTPATH), _
                          catScriptLibraryTypeVBAProject, _
                          mInfo(TAG_MDLNAME), _
                          mInfo(TAG_ENTRYPNT), _
                          Array())
End Sub

Attribute VB_Name = "Cat_Macro_Menu_Model"
'vba CATIA V5用　ﾏｸﾛ起動(ﾃﾇｷ)ﾒﾆｭｰ Ver0.0.1  by Kantoku
'Cat_Macro_Menu_Model.bas
'using-'KCL0.0.12'
'ﾀｸﾞを追記したﾓｼﾞｭｰﾙをﾌﾟﾛｼﾞｪｸﾄに追加するだけで
'自動的にﾎﾞﾀﾝを追加します

Const FormTitle = "Macro"

'----- ﾒﾆｭｰの仕様 お好みで ---------------------------------------

'ﾒﾆｭｰの表示方法
'True-ﾓｰﾀﾞﾚｽ表示  False-ﾓｰﾀﾞﾙ表示
Private Const MENU_SHOW_TYPE = True

'ﾒﾆｭｰを閉じるﾀｲﾐﾝｸﾞ
'True-ﾎﾞﾀﾝｸﾘｯｸ後閉じます  False-ﾌｫｰﾑのXﾎﾞﾀﾝを押して閉じます
Private Const MENU_HIDE_TYPE = True

'ﾒﾆｭｰのﾏﾙﾁﾍﾟｰｼﾞの設定
'変更する際は
'{ ﾀｸﾞのｸﾞﾙｰﾌﾟ番号 : ﾍﾟｰｼﾞのﾀｲﾄﾙ文字 }
'の状態にして下さい
Private Const GROUP_NUMBER_CAPTION = _
            "{ 1 : Part }" & _
            "{11 : Assy }" & _
            "{21 : Draw }" & _
            "{51 : Other }"
'-----------------------------------------------------------------

Option Explicit

'----- 設定用 変更しない方が良いと思います -----------------------

'ﾏﾙﾁﾍﾟｰｼﾞ用 ｸﾞﾙｰﾌﾟ設定
Private PageMap As Object

'ﾀｸﾞ
Private TagMap As Object                    'ｸﾞﾙｰﾌﾟ管理用

Private Const TAG_S = "{"                   'ﾀｸﾞｽﾀｰﾄ
Private Const TAG_D = ":"                   'ﾀｸﾞ区切り
Private Const TAG_E = "}"                   'ﾀｸﾞｴﾝﾄﾞ

Private Const TAG_GROUP = "gp"              'ﾀｸﾞｸﾞﾙｰﾌﾟ
Private Const TAG_ENTRYPNT = "ep"           'ﾀｸﾞｴﾝﾄﾘｰﾎﾟｲﾝﾄ
Private Const TAG_ENTRY_DEF = "CATMain"     'ﾀｸﾞｴﾝﾄﾘｰﾎﾟｲﾝﾄ 未定義時
Private Const TAG_PJTPATH = "pjt_path"      'ﾀｸﾞﾌﾟﾛｼﾞｪｸﾄﾊﾟｽ
Private Const TAG_MDLNAME = "mdl_name"      'ﾀｸﾞﾓｼﾞｭｰﾙ名
'-----------------------------------------------------------------

'ﾒﾆｭｰ ｴﾝﾄﾘｰﾎﾟｲﾝﾄ
Sub CATMain()
    
    'ﾏﾙﾁﾍﾟｰｼﾞ用 ｸﾞﾙｰﾌﾟ設定
    Set PageMap = Get_KeyValue(GROUP_NUMBER_CAPTION, True)
    
    'ﾎﾞﾀﾝ用情報取得
    Dim ButtonInfos As Object
    Set ButtonInfos = Get_ButtonInfo()
    If ButtonInfos Is Nothing Then
        MsgBox "ﾒﾆｭｰに表示するﾏｸﾛがありません", vbExclamation + vbOKOnly
        Exit Sub
    End If
    
    'ｸﾞﾙｰﾌﾟ順にｿｰﾄ
    Dim SoLst As Object
    Set SoLst = To_SortedList(ButtonInfos)
    If SoLst Is Nothing Then Exit Sub
    
    'View表示
    Dim Menu As Cat_Macro_Menu_View
    Set Menu = New Cat_Macro_Menu_View
    Call Menu.Set_FormInfo(SoLst, PageMap, FormTitle, MENU_HIDE_TYPE)
    
    If MENU_SHOW_TYPE Then
        Menu.Show vbModeless
    Else
        Menu.Show vbModal
    End If
End Sub


'******* ｻﾎﾟｰﾄ関数 *********

'ﾓｼﾞｭｰﾙからﾎﾞﾀﾝ用情報取得
'pram  :
'return: lst(Dict)
Private Function Get_ButtonInfo() As Object
    Set Get_ButtonInfo = Nothing
    
    Dim Apc As Object: Set Apc = GetApc()
    Dim ExecPjt As Object: Set ExecPjt = Apc.ExecutingProject
    Dim PjtPath As String: PjtPath = ExecPjt.DisplayName
    
    Dim AllComps As Object
    Set AllComps = GetModuleLst(ExecPjt.ProjectItems.VBComponents)
    If AllComps Is Nothing Then Exit Function
    
    Dim Comp As Object 'VBComponent
    Dim Mdl As Object 'CodeModule
    Dim DecCode As String
    Dim DecCnt As Long
    Dim MdlInfo As Object
    Dim CanExecMethod As String
    Dim BtnInfos As Object: Set BtnInfos = KCL.InitLst()
    
    For Each Comp In AllComps
        Set Mdl = Comp.CodeModule
        
        '宣言部位置
        DecCnt = Mdl.CountOfDeclarationLines
        If DecCnt < 1 Then GoTo Continue
        
        '宣言部ｺｰﾄﾞ
        DecCode = Mdl.Lines(1, Mdl.CountOfDeclarationLines)
        
        'ﾀｸﾞ取得
        Set MdlInfo = Get_KeyValue(DecCode)
        If MdlInfo Is Nothing Then GoTo Continue
        
        'Groupﾁｪｯｸ
        If Not MdlInfo.Exists(TAG_GROUP) Then GoTo Continue
        If IsNumeric(MdlInfo(TAG_GROUP)) Then
            MdlInfo(TAG_GROUP) = CLng(MdlInfo(TAG_GROUP))
        Else
            GoTo Continue
        End If
        Debug.Print TypeName(MdlInfo(TAG_GROUP)) & " : " & MdlInfo(TAG_GROUP)
        If Not PageMap.Exists(MdlInfo(TAG_GROUP)) Then GoTo Continue
        
        'ｴﾝﾄﾘｰﾎﾟｲﾝﾄﾁｪｯｸ
        CanExecMethod = vbNullString
        If MdlInfo.Exists(TAG_ENTRYPNT) Then
            If Exist_Method(Mdl, MdlInfo(TAG_ENTRYPNT)) Then
                CanExecMethod = MdlInfo(TAG_ENTRYPNT)
            Else
                GoTo Try_TAG_ENTRY_DEF
            End If
        Else
Try_TAG_ENTRY_DEF:
            If Exist_Method(Mdl, TAG_ENTRY_DEF) Then
                 CanExecMethod = TAG_ENTRY_DEF
            End If
        End If
        If CanExecMethod = vbNullString Then GoTo Continue
        Set MdlInfo = Push_Dic(MdlInfo, TAG_ENTRYPNT, CanExecMethod)
        
        Set MdlInfo = Push_Dic(MdlInfo, TAG_PJTPATH, PjtPath)
        Set MdlInfo = Push_Dic(MdlInfo, TAG_MDLNAME, Mdl.Name)
        
        BtnInfos.Add MdlInfo
Continue:
    Next
    
    If BtnInfos.Count < 1 Then Exit Function
    
    Set Get_ButtonInfo = BtnInfos
End Function

'Dictionaryに押し込み
'pram  : Dict,vri,vri
'return: Dict
Private Function Push_Dic(ByVal Dic As Object, _
                          ByVal Key As Variant, _
                          ByVal Val As Variant) As Object
    If Dic.Exists(Key) Then
        Dic(Key) = Val
    Else
        Dic.Add Key, Val
    End If
    Set Push_Dic = Dic
End Function

'ﾀｸﾞっぽいもの取得-ｵﾌﾟｼｮﾝはKeyをLong化
'pram  : str,Opt_bool
'return: Dict
Private Function Get_KeyValue( _
                    ByVal txt As String, _
                    Optional ByVal KeyToLong As Boolean = False) _
                    As Object
    Set Get_KeyValue = Nothing

    Dim Reg As Object
    Set Reg = CreateObject("VBScript.RegExp")
    With Reg
        .Pattern = TAG_S & "(.*?)" & TAG_D & "(.*?)" & TAG_E
        .Global = True
    End With
    
    Dim Matches As Object
    Set Matches = Reg.Execute(txt)
    Set Reg = Nothing
    
    If Matches.Count < 1 Then Exit Function
    
    Dim Dic As Object: Set Dic = KCL.InitDic(vbTextCompare)
    Dim Match As Object, SubMatchs As Object
    Dim Key As Variant, Var As Variant
    
    For Each Match In Matches
        Set SubMatchs = Match.SubMatches
        
        If SubMatchs.Count < 2 Then GoTo Continue
        
        Key = Trim(Replace(SubMatchs(0), """", ""))
        If Len(Key) < 1 Then GoTo Continue
        If KeyToLong Then Key = CLng(Key)
        
        Var = Trim(Replace(SubMatchs(1), """", ""))
        If Len(Var) < 1 Then GoTo Continue
        
        Set Dic = Push_Dic(Dic, Key, Var)
Continue:
    Next
    
    If Dic.Count < 1 Then Exit Function
    
    Set Get_KeyValue = Dic
End Function

'ｸﾞﾙｰﾌﾟをｷｰとしたｿｰﾄ済みﾘｽﾄ
'pram  :lst(Dict)
'return: Dict(lst(Dict))
Private Function To_SortedList(ByVal Infos As Object) As Object
    Set To_SortedList = Nothing
    
    Dim SoLst As Object
    Set SoLst = CreateObject("System.Collections.SortedList")
    Dim Lst As Object
    
    Dim Info As Object
    For Each Info In Infos
        If SoLst.ContainsKey(Info(TAG_GROUP)) = True Then
            SoLst(Info(TAG_GROUP)).Add Info
        Else
            Set Lst = KCL.InitLst()
            Lst.Add Info
            SoLst.Add Info(TAG_GROUP), Lst
        End If
    Next
    
    If SoLst.Count < 1 Then Exit Function
    
    'ﾓｼﾞｭｰﾙ名でｿｰﾄ
    Dim i As Long
    Dim InfoDic As Object: Set InfoDic = KCL.InitDic(vbTextCompare)
    For i = 0 To SoLst.Count - 1
        InfoDic.Add SoLst.GetKey(i), Sort_by(SoLst.GetByIndex(i))
    Next
    
    Set To_SortedList = InfoDic
End Function

'ﾓｼﾞｭｰﾙ名でｿｰﾄ
'pram  :lst(Dict)
'return: lst(Dict)
Private Function Sort_by(ByVal Lst As Object) As Object
    Dim tmp As Object
    Dim i As Long, j As Long
    Set tmp = Lst(0)
    For i = 0 To Lst.Count - 1
        For j = Lst.Count - 1 To i Step -1
            If Lst(i)(TAG_MDLNAME) > Lst(j)(TAG_MDLNAME) Then
                Set tmp = Lst(i)
                Set Lst(i) = Lst(j)
                Set Lst(j) = tmp
            End If
        Next j
    Next i
    Set Sort_by = Lst
End Function


'******* APC/VBE *********

'Apc取得
'pram  :
'return: obj-IApc
Private Function GetApc() As Object
    Set GetApc = Nothing
    
    'VBAﾊﾞｰｼﾞｮﾝﾁｪｯｸ
    Dim COMObjectName$
    #If VBA7 Then
        COMObjectName = "MSAPC.Apc.7.1"
    #ElseIf VBA6 Then
        COMObjectName = "MSAPC.Apc.6.2"
    #Else
        MsgBox "VBAのﾊﾞｰｼﾞｮﾝが未対応です"
        Exit Function
    #End If
    
    'APC取得
    Dim Apc As Object: Set Apc = Nothing
    On Error Resume Next
        Set Apc = CreateObject(COMObjectName)
    On Error GoTo 0
    
    If Apc Is Nothing Then
        MsgBox "MSAPC.Apcが取得できませんでした"
        Exit Function
    End If
    
    Set GetApc = Apc
End Function

'ﾌﾟﾛｼｰｼﾞｬの存在ﾁｪｯｸ - Privateの判断していない
'pram  : obj-CodeModule,str
'return: Boolean
Private Function Exist_Method(ByVal CodeMdl As Object, _
                              ByVal Name As String) As Boolean
    Dim tmp As Long
    On Error Resume Next
        tmp = CodeMdl.ProcBodyLine(Name, 0)
    On Error GoTo 0
    Exist_Method = tmp > 0
    Err.Number = 0
End Function

'ﾓｼﾞｭｰﾙ取得
'pram  : obj-VBComponents
'return: lst(obj-VBComponent)

'vbext_ComponentType
'1-vbext_ct_StdModule 2-vbext_ct_ClassModule 3-vbext_ct_MSForm
Private Function GetModuleLst(ByVal Itms As Object) As Object
    Set GetModuleLst = Nothing
    Dim Lst As Object: Set Lst = KCL.InitLst()
    Dim Itm As Object
    For Each Itm In Itms
        If Not Itm.Type = 1 Then GoTo Continue 'vbext_ComponentType
        Lst.Add Itm
Continue:
    Next
    If Lst.Count < 1 Then Exit Function
    Set GetModuleLst = Lst
End Function

Attribute VB_Name = "Cat_Macro_Menu_View"
Attribute VB_Base = "0{D5A2E7AA-6322-47BA-A80A-B248B8C20F45}{C8F8ACA0-2EE4-4644-A9E2-E93487D3F2A2}"
Attribute VB_GlobalNameSpace = False
Attribute VB_Creatable = False
Attribute VB_PredeclaredId = True
Attribute VB_Exposed = False
Attribute VB_TemplateDerived = False
Attribute VB_Customizable = False

'vba CATIA V5用　ﾏｸﾛ起動(ﾃﾇｷ)ﾒﾆｭｰ  by Kantoku
'Cat_Macro_Menu_View.frm
'ﾒﾆｭｰのUIです。

'ﾌｫｰﾑ
Private FrmMargin As Variant '上,下,左,右のﾎﾞﾀﾝ配置のﾏｰｼﾞﾝ
Private Const ADJUST_F_W = 13 'ﾌｫｰﾑの左右の調整幅
Private Const ADJUST_F_H = 30 'ﾌｫｰﾑの上下の調整幅

'ﾏﾙﾁﾍﾟｰｼﾞ
Private Const ADJUST_M_W = 5 'ﾏﾙﾁﾍﾟｰｼﾞの左右の調整幅
Private Const ADJUST_M_H = 18 'ﾏﾙﾁﾍﾟｰｼﾞの上下の調整幅

'ﾎﾞﾀﾝ
Private Const BTN_W = 70 'ﾎﾞﾀﾝの幅-ﾌｫｰﾑの最低幅以下にすると余白が増える
Private Const BTN_H = 20 'ﾎﾞﾀﾝ1個の高さ


Private mBtns As Object 'ｲﾍﾞﾝﾄ

Option Explicit

'ﾌｫｰﾑ生成情報取得
Sub Set_FormInfo(ByVal InfoLst As Object, _
                 ByVal PageMap As Object, _
                 ByVal FormTitle As String, _
                 ByVal CloseType As Boolean)
                 
    '配列定数欲しい･･･
    FrmMargin = Array(5, 5, 5, 5) '上,下,左,右のﾎﾞﾀﾝ配置のﾏｰｼﾞﾝ
                 
    'ﾏﾙﾁﾍﾟｰｼﾞ
    Dim MPgs As MultiPage
    Set MPgs = Me.Controls.Add("Forms.MultiPage.1", 1, True)
    
    Dim Pgs As Pages
    Set Pgs = MPgs.Pages
    Pgs.Clear
    
    Dim Key As Long, KeyStr As Variant
    Dim Pg As Page, PName As String
    Dim BtnInfos As Object, Info As Variant
    Dim Btns As Object: Set Btns = KCL.InitLst()
    Dim Btn As MSForms.CommandButton
    Dim BtnEvt As Button_Evt
    
    For Each KeyStr In InfoLst
    
        'ﾍﾟｰｼﾞ
        Key = CLng(KeyStr)
        If Not PageMap.Exists(Key) Then GoTo Continue
        
        PName = PageMap(Key)
        Set Pg = Get_Page(Pgs, PName)
        
        'ﾎﾞﾀﾝ
        Set BtnInfos = InfoLst(KeyStr)
        For Each Info In BtnInfos
            Set Btn = Init_Button(Pg.Controls, Key, Info)
            Set BtnEvt = New Button_Evt
            Call BtnEvt.set_Event(Btn, Info, Me, CloseType)
            Btns.Add BtnEvt
        Next
Continue:
    Next
    
    'ｲﾍﾞﾝﾄ
    Set mBtns = Btns
    
    'ﾏﾙﾁﾍﾟｰｼﾞ
    Call Set_MPage(MPgs)
    
    'ﾌｫｰﾑ
    Call Set_Form(MPgs, FormTitle)
End Sub

'ﾌｫｰﾑ設定
Private Sub Set_Form(ByVal MPgs As MultiPage, ByVal Cap As String)
    With Me
        .Height = MPgs.Height + ADJUST_F_H
        .Width = MPgs.Width + ADJUST_F_W
        .Caption = Cap
    End With
End Sub

'ﾏﾙﾁﾍﾟｰｼﾞ設定
Private Sub Set_MPage(ByVal MPgs As MultiPage)
    MPgs.Width = FrmMargin(1) + BTN_W + FrmMargin(3) + ADJUST_M_W
    
    Dim Pg As Page
    Dim MaxBtnCnt As Long: MaxBtnCnt = 0
    Dim BtnCnt As Long
    For Each Pg In MPgs.Pages
        BtnCnt = Pg.Controls.Count
        MaxBtnCnt = IIf(BtnCnt > MaxBtnCnt, BtnCnt, MaxBtnCnt)
    Next
    MPgs.Height = FrmMargin(0) + (BTN_H * MaxBtnCnt) + FrmMargin(2) + ADJUST_M_H
End Sub

'ﾎﾞﾀﾝ作成
Private Function Init_Button(ByVal Ctls As Controls, _
                             ByVal Idx As Long, _
                             ByVal BtnInfo As Variant) As MSForms.CommandButton
    Dim Btn As MSForms.CommandButton
    Set Btn = Ctls.Add("Forms.CommandButton.1", Idx, True)
    
    Dim Pty As Variant
    For Each Pty In BtnInfo.keys
        Call Try_SetProperty(Btn, Pty, BtnInfo.Item(Pty))
    Next
    
    With Btn
        .Top = FrmMargin(0) + (Ctls.Count - 1) * BTN_H
        .Left = FrmMargin(2)
        .Height = BTN_H
        .Width = BTN_W
    End With
    
    Set Init_Button = Btn
End Function

'ﾎﾞﾀﾝﾌﾟﾛﾊﾟﾃｨの設定
Private Sub Try_SetProperty(ByVal Ctrl As Object, _
                            ByVal PptyName As String, _
                            ByVal Value As Variant)
    On Error Resume Next
        Err.Number = 0
        
        Dim tmp As Variant
        tmp = CallByName(Ctrl, PptyName, VbGet)
        If Not Err.Number = 0 Then
            Debug.Print PptyName & ":ﾌﾟﾛﾊﾟﾃｨ名の不正(" & Err.Number & ")"
            Exit Sub
        End If
        
        Select Case TypeName(tmp)
            Case "Empty"
                Exit Sub
            Case "Long"
                Value = CLng(Value)
            Case "Boolean"
                Value = CBool(Value)
            Case "Currency"
                Value = CCur(Value)
        End Select
        If Not Err.Number = 0 Then
            Debug.Print Value & ":値の型変換の不正(" & Err.Number & ")"
            Exit Sub
        End If
        
        Call CallByName(Ctrl, PptyName, VbLet, Value)
        If Not Err.Number = 0 Then
            Debug.Print Value & ":ﾌﾟﾛﾊﾟﾃｨ設定の不正(" & Err.Number & ")"
            Exit Sub
        End If
    On Error GoTo 0
End Sub

'ﾍﾟｰｼﾞ取得-無ければ作成
Private Function Get_Page(ByVal Pgs As Pages, ByVal Name As String) As Page
    Dim Pg As Page
    On Error Resume Next
        Set Pg = Pgs.Item(Name)
    On Error GoTo 0
    
    If Pg Is Nothing Then
        Set Pg = Pgs.Add(Name, Name, Pgs.Count)
    End If
    
    Set Get_Page = Pg
End Function

Attribute VB_Name = "KCL"
'vba Kantoku_CATVBA_Library ver0.0.12
'KCL.bas - 標準ﾓｼﾞｭｰﾙ
Option Explicit

Private mSW& '時間計測用

#If VBA7 And Win64 Then
    Private Declare PtrSafe Function timeGetTime Lib "winmm.dll" () As Long
#Else
    Private Declare Function timeGetTime Lib "winmm.dll" () As Long
#End If

'開発用-ｵﾌﾞｼﾞｪｸﾄﾁｪｯｸ
Sub CATMain()
    Dim Msg$: Msg = "選択して下さい : ESCｷｰ 終了"
    Dim SI As AnyObject
    Dim Doc As Document: Set Doc = CATIA.ActiveDocument
    Do
        Set SI = SelectItem(Msg)
        If IsNothing(SI) Then Exit Do
        Stop
    Loop
End Sub

'*****CATIAな関数*****
'ﾏｸﾛｽﾀｰﾄﾁｪｯｸ
''' @param:DocTypes-array(string),string ﾏｸﾛ実行を許可するﾄﾞｷｭﾒﾝﾄのﾀｲﾌﾟ
''' @return:Boolean
Public Function CanExecute(ByVal DocTypes As Variant) As Boolean
    CanExecute = False
    
    If CATIA.Windows.Count < 1 Then
        MsgBox "ﾌｧｲﾙが開かれていません"
        Exit Function
    End If
    
    If VarType(DocTypes) = vbString Then DocTypes = Split(DocTypes, ",")
    If Not IsFilterType(DocTypes) Then Exit Function
    
    Dim ErrMsg As String
    ErrMsg = "ﾌｧｲﾙのﾀｲﾌﾟが異なります。" + vbNewLine + "(" + Join(DocTypes, ",") + " のみです)"
    
    Dim ActDoc As Document
    On Error Resume Next
        Set ActDoc = CATIA.ActiveDocument
    On Error GoTo 0
    If ActDoc Is Nothing Then
        MsgBox ErrMsg, vbExclamation + vbOKOnly
        Exit Function
    End If
    
    If UBound(Filter(DocTypes, TypeName(ActDoc))) < 0 Then
        MsgBox ErrMsg, vbExclamation + vbOKOnly
        Exit Function
    End If
    
    CanExecute = True
End Function

'選択
''' @param:Msg-ﾒｯｾｰｼﾞ
''' @param:Filter-array(string),string 選択ﾌｨﾙﾀｰ(指定無し時AnyObject)
''' @return:AnyObject
Public Function SelectItem(ByVal Msg$, _
                           Optional ByVal Filter As Variant = Empty) _
                           As AnyObject
    Dim SE As SelectedElement
    Set SE = SelectElement(Msg, Filter)
    
    If IsNothing(SE) Then
        Set SelectItem = SE
    Else
        Set SelectItem = SE.Value
    End If
End Function

'選択
''' @param:Msg-ﾒｯｾｰｼﾞ
''' @param:Filter-array(string),string 選択ﾌｨﾙﾀｰ(指定無し時AnyObject)
''' @return:SelectedElement
Public Function SelectElement(ByVal Msg$, _
                           Optional ByVal Filter As Variant = Empty) _
                           As SelectedElement
    If IsEmpty(Filter) Then Filter = Array("AnyObject")
    If VarType(Filter) = vbString Then Filter = ToStrVriAry(Filter)
    If Not IsFilterType(Filter) Then Exit Function
    
    Dim Sel As Variant: Set Sel = CATIA.ActiveDocument.Selection
    Sel.Clear
    Select Case Sel.SelectElement2(Filter, Msg, False)
        Case "Cancel", "Undo", "Redo"
            Exit Function
    End Select
    Set SelectElement = Sel.Item(1)
    Sel.Clear
End Function

'InternalName
''' @param:AOj-AnyObject
''' @return:String
Public Function GetInternalName$(ByVal AOj As AnyObject)
    If IsNothing(AOj) Then
        GetInternalName = Empty: Exit Function
    End If
    GetInternalName = AOj.GetItem("ModelElement").InternalName
End Function

'T型のParent取得 Nameでのﾁｪｯｸも必要
''' @param:AOj-AnyObject
''' @param:T-String
''' @return:AnyObject
Public Function GetParent_Of_T(ByVal AOj As AnyObject, ByVal T$) As AnyObject
    If TypeName(AOj) = TypeName(AOj.Parent) And _
       AOj.Name = AOj.Parent.Name Then
        Set GetParent_Of_T = Nothing
        Exit Function
    End If
    If TypeName(AOj) = T Then
        Set GetParent_Of_T = AOj
    Else
        Set GetParent_Of_T = GetParent_Of_T(AOj.Parent, T)
    End If
End Function

'BrepNameの取得
''' @param:MyBRepName-String
''' @return:String
Public Function GetBrepName(MyBRepName As String) As String
    MyBRepName = Replace(MyBRepName, "Selection_", "")
    MyBRepName = Left(MyBRepName, InStrRev(MyBRepName, "));"))
    MyBRepName = MyBRepName + ");WithPermanentBody;WithoutBuildError;WithSelectingFeatureSupport;MFBRepVersion_CXR15)"
    GetBrepName = MyBRepName
End Function

'言語取得
'return-ISO 639-1 code
'https://ja.wikipedia.org/wiki/ISO_639-1%E3%82%B3%E3%83%BC%E3%83%89%E4%B8%80%E8%A6%A7
Public Function GetLanguage() As String
    GetLanguage = "non"
    If CATIA.Windows.Count < 1 Then Exit Function
    GetLanguage = "other"
    CATIA.ActiveDocument.Selection.Clear
    Dim St As String: St = CATIA.StatusBar
    Select Case True
        Case ExistsKey(St, "object")
            '英語-Select an object or a command
            GetLanguage = "en"
        Case ExistsKey(St, "objet")
            'フランス語-Selectionnez un objet ou une commande
            GetLanguage = "fr"
        Case ExistsKey(St, "Objekt")
            'ドイツ語-Ein Objekt oder einen Befehl auswahlen
            GetLanguage = "de"
        Case ExistsKey(St, "oggetto")
            'イタリア語-Selezionare un oggetto o un comando
            GetLanguage = "it"
        Case ExistsKey(St, "ｵﾌﾞｼﾞｪｸﾄ")
            '日本語-ｵﾌﾞｼﾞｪｸﾄまたはｺﾏﾝﾄﾞを選択してください
            GetLanguage = "ja"
        Case ExistsKey(St, "объект")
            'ロシア語-Выберите объект или команду
            GetLanguage = "ru"
        Case ExistsKey(St, "象或")
            '中国語-???象或?羅
            GetLanguage = "zh"
        Case Else
            Select Case Len(St)
                Case 13
                    '韓国語-???? ?? ?? ??　unicode未対応の為
                    GetLanguage = "ko"
                Case 23
                    '日本語-日本語版以外のため
                    GetLanguage = "ja"
                Case Else
                    'それ以外
            End Select
    End Select
End Function

'文字列内に指定文字が存在するか？
'大文字小文字は無視
Private Function ExistsKey(ByVal txt As String, ByVal Key As String) As Boolean
    ExistsKey = IIf(InStr(LCase(txt), LCase(Key)) > 0, True, False)
End Function

'文字型配列?
Private Function IsStringAry(ByVal ary As Variant) As Boolean
    IsStringAry = False
    
    If Not IsArray(ary) Then Exit Function
    Dim i&
    For i = 0 To UBound(ary)
        If Not VarType(ary(i)) = vbString Then Exit Function
    Next
    
    IsStringAry = True
End Function

'ﾌｨﾙﾀｰﾀｲﾌﾟとしてOK?
Private Function IsFilterType(ByVal ary As Variant) As Boolean
    IsFilterType = False
    Dim ErrMsg$: ErrMsg = "ﾌｨﾙﾀｰ又はﾄﾞｷｭﾒﾝﾄﾀｲﾌﾟの指定は" + vbNewLine + _
                          "Variant(String)型配列で行ってください" + vbNewLine + _
                          "(ﾏｸﾛｺｰﾄﾞのｴﾗｰです)"
    
    If Not IsStringAry(ary) Then
        MsgBox ErrMsg
        Exit Function
    End If
    
    IsFilterType = True
End Function

'文字型からﾊﾞﾘｱﾝﾄ配列生成(CATIAの為にすごく無駄･･･)
Private Function ToStrVriAry(ByVal s$) As Variant
    Dim ary As Variant: ary = Split(s, ",")
    Dim vriary() As Variant: ReDim vriary(UBound(ary))
    Dim i&
    For i = 0 To UBound(ary)
        vriary(i) = ary(i)
    Next
    ToStrVriAry = vriary
End Function

'*****ｼｽﾃﾑな関数*****
'Nothing 書き方に統一感が無い為
''' @param:OJ-Variant(Of Object)
''' @return:Boolean
Public Function IsNothing(ByVal Oj As Variant) As Boolean
    IsNothing = Oj Is Nothing
End Function

'Scripting.Dictionary
''' @param:CompareMode-Long
''' @return:Object(Of Dictionary)
Public Function InitDic(Optional CompareMode As Long = vbBinaryCompare) As Object
    Dim Dic As Object
    Set Dic = CreateObject("Scripting.Dictionary")
    Dic.CompareMode = CompareMode
    Set InitDic = Dic
End Function

'ArrayList
''' @return:Object(Of ArrayList)Public
Function InitLst() As Object
    Set InitLst = CreateObject("System.Collections.ArrayList")
End Function

'型ﾁｪｯｸ
''' @param:OJ-Object
''' @param:T-String
''' @return:Boolean
Public Function IsType_Of_T(ByVal Oj As Object, ByVal T$) As Boolean
    IsType_Of_T = IIf(TypeName(Oj) = T, True, False)
End Function


'*****配列な関数*****
'配列の連結
''' @param:Ary1-Variant(Of Array)
''' @param:Ary2-Variant(Of Array)
''' @return:Variant(Of Array)
Public Function JoinAry(ByVal Ary1 As Variant, ByVal Ary2 As Variant)
    Select Case True
        Case Not IsArray(Ary1) And Not IsArray(Ary2)
            JoinAry = Empty: Exit Function
        Case Not IsArray(Ary1)
            JoinAry = Ary2: Exit Function
        Case Not IsArray(Ary2)
            JoinAry = Ary1: Exit Function
    End Select
    Dim StCount&: StCount = UBound(Ary1)
    ReDim Preserve Ary1(UBound(Ary1) + UBound(Ary2) + 1)
    Dim i&
    If IsObject(Ary2(0)) Then
        For i = StCount + 1 To UBound(Ary1)
            Set Ary1(i) = Ary2(i - StCount - 1)
        Next
    Else
        For i = StCount + 1 To UBound(Ary1)
            Ary1(i) = Ary2(i - StCount - 1)
        Next
    End If
    JoinAry = Ary1
End Function

'配列の抽出
''' @param:Ary-Variant(Of Array)
''' @param:StartIdx-Long
''' @param:EndIdx-Long
''' @return:Variant(Of Array)
Public Function GetRangeAry(ByVal ary As Variant, ByVal StartIdx&, ByVal EndIdx&) As Variant
    If Not IsArray(ary) Then Exit Function
    If EndIdx - StartIdx < 0 Then Exit Function
    If StartIdx < 0 Then Exit Function
    If EndIdx > UBound(ary) Then Exit Function
    
    Dim RngAry() As Variant: ReDim RngAry(EndIdx - StartIdx)
    Dim i&
    For i = StartIdx To EndIdx
        RngAry(i - StartIdx) = ary(i)
    Next
    GetRangeAry = RngAry
End Function

'配列のｸﾛｰﾝ
''' @param:Ary-Variant(Of Array)
''' @return:Variant(Of Array)
Public Function CloneAry(ByVal ary As Variant) As Variant
    If Not IsArray(ary) Then Exit Function
    CloneAry = GetRangeAry(ary, 0, UBound(ary))
End Function

'配列の値が一致するか?
''' @param:Ary1-Variant(Of Array)
''' @param:Ary2-Variant(Of Array)
''' @return:Boolean
Public Function IsAryEqual(ByVal Ary1 As Variant, ByVal Ary2 As Variant) As Boolean
    IsAryEqual = False
    If Not IsArray(Ary1) Or Not IsArray(Ary2) Then Exit Function
    If Not UBound(Ary1) = UBound(Ary2) Then Exit Function
    Dim i&
    For i = 0 To UBound(Ary1)
        If Not Ary1(i) = Ary2(i) Then Exit Function
    Next
    IsAryEqual = True
End Function


'*****IOな関数*****
'FileSystemObject
''' @return:Object(Of FileSystemObject)
Public Function GetFSO() As Object
    Set GetFSO = CreateObject("Scripting.FileSystemObject")
End Function

'ﾊﾟｽ/ﾌｧｲﾙ名/拡張子 分割
''' @param:FullPath-ﾌｧｲﾙﾊﾟｽ
''' @return:Variant(Of Array(Of String)) (0-Path 1-BaseName 2-Extension)
Public Function SplitPathName(ByVal FullPath$) As Variant
    Dim Path(2) As String
    With GetFSO
        Path(0) = .getParentFolderName(FullPath)
        Path(1) = .GetBaseName(FullPath)
        Path(2) = .GetExtensionName(FullPath)
    End With
    SplitPathName = Path
End Function

'ﾊﾟｽ/ﾌｧｲﾙ名/拡張子 連結
''' @param:Path-Variant(Of Array(Of String)) (0-Path 1-BaseName 2-Extension)
''' @return:ﾌｧｲﾙﾊﾟｽ
Public Function JoinPathName$(ByVal Path As Variant)
    If Not IsArray(Path) Then Stop '未対応
    If Not UBound(Path) = 2 Then Stop '未対応
    JoinPathName = Path(0) + "\" + Path(1) + "." + Path(2)
End Function

'ﾌｧｲﾙ,ﾌｫﾙﾀﾞの有無
''' @param:Path-ﾊﾟｽ
''' @return:Boolean
Public Function IsExists(ByVal Path$) As Boolean
    IsExists = False
    Dim Fso As Object: Set Fso = GetFSO
    If Fso.FileExists(Path) Then
        IsExists = True: Exit Function 'ﾌｧｲﾙ
    ElseIf Fso.FolderExists(Path) Then
        IsExists = True: Exit Function 'ﾌｫﾙﾀﾞ
    End If
    Set Fso = Nothing
End Function

'重複しない名前取得
''' @param:Path-ﾌｧｲﾙﾊﾟｽ
''' @return:新たなﾌｧｲﾙﾊﾟｽ
Public Function GetNewName$(ByVal OldPath$)
    Dim Path As Variant
    Path = SplitPathName(OldPath)
    Path(2) = "." & Path(2)
    Dim NewPath$: NewPath = Path(0) + "\" + Path(1)
    If Not IsExists(NewPath + Path(2)) Then
        GetNewName = NewPath + Path(2)
        Exit Function
    End If
    Dim TempName$, i&: i = 0
    Do
        i = i + 1
        TempName = NewPath + "_" + CStr(i) + Path(2)
        If Not IsExists(TempName) Then
            GetNewName = TempName
            Exit Function
        End If
    Loop
End Function

'ﾌｧｲﾙの書き込み
''' @param:Path-ﾌｧｲﾙﾊﾟｽ
''' @param:Txt-String
Public Sub WriteFile(ByVal Path$, ByVal txt) '$)
    Call GetFSO.OpenTextFile(Path, 2, True).Write(txt)
End Sub

'ﾌｧｲﾙ読み込み
''' @param:Path-ﾌｧｲﾙﾊﾟｽ
''' @return:Variant(Of Array(Of String))
Public Function ReadFile(ByVal Path$) As Variant
    With GetFSO.GetFile(Path).OpenAsTextStream
        ReadFile = Split(.ReadAll, vbNewLine)
        .Close
    End With
End Function


'*****ｽﾄｯﾌﾟｳｫｯﾁな関数*****
'時間計測スタート
Public Sub SW_Start()
    mSW = timeGetTime
End Sub

'計測取得
''' @return:Double(Unit:s)
Public Function SW_GetTime#()
    SW_GetTime = IIf(mSW = 0, -1, (timeGetTime - mSW) * 0.001)
End Function

Attribute VB_Name = "sample_Draft_View_Lock_UnLock"
'vba sample_Draft_View_Lock_UnLock ver0.0.2  using-'KCL0.0.12'  by Kantoku
'ｱｸﾃｨﾌﾞなｼｰﾄの全ﾋﾞｭｰをﾛｯｸ・ｱﾝﾛｯｸ

'{GP:21}
'{Caption:Lock_UnLock}
'{ControlTipText:ｱｸﾃｨﾌﾞなｼｰﾄの全ﾋﾞｭｰをﾛｯｸ・ｱﾝﾛｯｸします}
'{BackColor:12648447}

Option Explicit

Sub CATMain()
    'ﾄﾞｷｭﾒﾝﾄのﾁｪｯｸ
    If Not CanExecute("DrawingDocument") Then Exit Sub
    
    Dim Views As DrawingViews
    Set Views = CATIA.ActiveDocument.Sheets.ActiveSheet.Views
    
    If Views.Count < 3 Then Exit Sub
    
    Dim View As DrawingView
    Set View = Views.Item(3)
    
    Dim LockState As Boolean
    LockState = View.LockStatus
    
    Dim Msg As String
    If LockState Then
        Msg = "ｱﾝﾛｯｸ"
        LockState = False
    Else
        Msg = "ﾛｯｸ"
        LockState = True
    End If
    
    Dim i As Long
    For i = 3 To Views.Count
        Set View = Views.Item(i)
        View.LockStatus = LockState
    Next
    
    MsgBox "全てのビューを" & Msg & "しました"
End Sub

Attribute VB_Name = "sample_IsExists_LeftAxis"
'vba sample_IsExists_LeftAxis_ver0.0.1  using-'KCL0.0.12'  by Kantoku
'Part内の左手座標系の有無ﾁｪｯｸ

'{Gp:1}
'{Ep:LeftHand}
'{Caption:LeftHandAxis}
'{ControlTipText:Part内の左手座標系の有無ﾁｪｯｸ}
'{BackColor:33023}

Option Explicit

Sub LeftHand()
    'ﾄﾞｷｭﾒﾝﾄのﾁｪｯｸ
    If Not CanExecute("PartDocument") Then Exit Sub
    
    Dim Doc As PartDocument: Set Doc = CATIA.ActiveDocument
    Dim Axs As AxisSystems: Set Axs = Doc.part.AxisSystems
    
    Dim Ax As AxisSystem
    Dim Msg As String: Msg = vbNullString
    For Each Ax In Axs
        If IsLeft(Ax) Then
            Msg = Msg & Ax.Name & vbNewLine
        End If
    Next
    
    If Msg = vbNullString Then
        MsgBox "左手系座標軸が存在していません"
    Else
        MsgBox "左手系座標軸が存在しています" & vbNewLine & Msg
    End If
End Sub

'左手系座標軸ﾁｪｯｸ
'Ax As AxisSystem←NG
Private Function IsLeft(ByVal Ax As Variant) As Boolean
    '軸ﾍﾞｸﾄﾙ
    Dim VecX(2), VecY(2), VecZ(2)
    Ax.GetXAxis VecX
    Ax.GetYAxis VecY
    Ax.GetZAxis VecZ
    
    'X軸/Y軸の外積
    Dim Outer(2) As Double
    Outer(0) = VecX(1) * VecY(2) - VecX(2) * VecY(1)
    Outer(1) = VecX(2) * VecY(0) - VecX(0) * VecY(2)
    Outer(2) = VecX(0) * VecY(1) - VecX(1) * VecY(0)
    
    ' 求めた外積とZ軸との内積を求める
    IsLeft = _
        VecZ(0) * Outer(0) + VecZ(1) * Outer(1) + VecZ(2) * Outer(2) < 0
End Function

Attribute VB_Name = "sample_Part2Product"
'vba sample_Part2Product_ver0.0.3  using-'KCL0.0.12'  by Kantoku
'PartからProduct化します
'ﾎﾞﾃﾞｨ･形状ｾｯﾄ･時系列形状ｾｯﾄで表示されているもののみ
'(ｽｹｯﾁは対象外)

'{GP:1}
'{Caption:Pt→Pro}
'{ControlTipText:PartからProductに変換します}

Option Explicit

Sub CATMain()
    'ﾄﾞｷｭﾒﾝﾄのﾁｪｯｸ
    If Not CanExecute("PartDocument") Then Exit Sub
    
    'Part
    Dim BaseDoc As PartDocument: Set BaseDoc = CATIA.ActiveDocument
    
    Dim BasePath As Variant: BasePath = Array(BaseDoc.FullName)
    
    Dim Pt As part: Set Pt = BaseDoc.part
    
    Dim LeafItems As Collection: Set LeafItems = Get_LeafItemLst(Pt.Bodies)
    
    Dim Msg As String
    If LeafItems Is Nothing Then
        Msg = "ｺﾋﾟｰ可能な要素がありません!"
        MsgBox Msg, vbOKOnly + vbExclamation
        Exit Sub
    End If
    
    '確認
    Msg = LeafItems.Count & "個のｺﾋﾟｰ可能な要素があります。" & vbNewLine & _
          "ﾍﾟｰｽﾄするﾀｲﾌﾟを指定してください" & vbNewLine & vbNewLine & _
          "はい : ﾘﾝｸの結果として(As Result With Link)" & vbNewLine & _
          "いいえ : 結果として(As Result)" & vbNewLine & _
          "キャンセル : マクロ中止"
    Dim PasteType As String
    Select Case MsgBox(Msg, vbQuestion + vbYesNoCancel)
        Case vbYes
            PasteType = "CATPrtResult"
        Case vbNo
            PasteType = "CATPrtResultWithOutLink"
        Case Else
            Exit Sub
    End Select
    
    KCL.SW_Start
    
    Dim BaseScene As Variant: BaseScene = GetScene3D(GetViewPnt3D())
    
    'Assy
    Dim TopDoc As ProductDocument: Set TopDoc = CATIA.Documents.Add("Product")
    
    Call ToProduct(TopDoc, LeafItems, PasteType)
    
    Call UpdateScene(BaseScene)
    TopDoc.Product.Update
    
    Debug.Print "Time:" & KCL.SW_GetTime & "s"
    MsgBox "Done"
End Sub

'Productにﾍﾟｰｽﾄ
Private Sub ToProduct(ByVal TopDoc As ProductDocument, _
                      ByVal LeafItems As Collection, _
                      ByVal PasteType As String)
    Dim TopSel As Selection
    Set TopSel = TopDoc.Selection
    
    Dim BaseSel As Selection
    Set BaseSel = KCL.GetParent_Of_T(LeafItems(1), "PartDocument").Selection
    
    Dim Prods As Products
    Set Prods = TopDoc.Product.Products
    
    Dim Itm As AnyObject
    Dim TgtDoc As PartDocument
    Dim ProdsNameDic As Object: Set ProdsNameDic = KCL.InitDic()
    
    CATIA.HSOSynchronized = False
    
    For Each Itm In LeafItems
        If ProdsNameDic.Exists(Itm.Name) Then
            Set TgtDoc = ProdsNameDic.Item(Itm.Name)
        Else
            Set TgtDoc = Init_Part(Prods, Itm.Name)
            ProdsNameDic.Add Itm.Name, TgtDoc
        End If
        
        Call Preparing_Copy(BaseSel, Itm)
        With BaseSel
            .Copy
            .Clear
        End With
        
        With TopSel
            .Clear
            .Add TgtDoc.part
            .PasteSpecial PasteType
        End With
    Next
    BaseSel.Clear
    TopSel.Clear
    CATIA.HSOSynchronized = True
End Sub

'ｺﾋﾟｰ要素を選択状態にする
Private Sub Preparing_Copy(ByVal Sel As Selection, ByVal Itm As AnyObject)
    Sel.Clear
    
    'Body
    If TypeName(Itm) = "Body" Then
        Sel.Add Itm
        Exit Sub
    End If
    
    'HybridBody
    Dim ShpsLst As Collection: Set ShpsLst = New Collection
    ShpsLst.Add Itm.HybridShapes
    
    Select Case TypeName(Itm)
        Case "HybridBody"
            Set ShpsLst = Get_All_HbShapes(Itm, ShpsLst)
        Case "OrderedGeometricalSet"
            Set ShpsLst = Get_All_OdrGeoSetShapes(Itm, ShpsLst)
    End Select
    
    Dim Shps As HybridShapes, Shp As HybridShape
    For Each Shps In ShpsLst
        For Each Shp In Shps
            Sel.Add Shp
        Next
    Next
End Sub

'指定時系列形状ｾｯﾄ以下の全てHybridShapesを取得
'再帰　かなり効率悪いかも
Private Function Get_All_OdrGeoSetShapes(ByVal OdrGeoSet As OrderedGeometricalSet, _
                                         ByVal Lst As Collection) As Collection
    Dim Child As OrderedGeometricalSet
    For Each Child In OdrGeoSet.OrderedGeometricalSets
        Lst.Add Child.HybridShapes
        If Child.OrderedGeometricalSets.Count > 0 Then
            Set Lst = Get_All_OdrGeoSetShapes(Child, Lst)
        End If
    Next
    Set Get_All_OdrGeoSetShapes = Lst
End Function

'指定形状ｾｯﾄ以下の全てHybridShapesを取得
'再帰　かなり効率悪いかも
Private Function Get_All_HbShapes(ByVal Hbdy As HybridBody, _
                                  ByVal Lst As Collection) As Collection
    Dim Child As HybridBody
    For Each Child In Hbdy.hybridBodies
        Lst.Add Child.HybridShapes
        If Child.hybridBodies.Count > 0 Then
            Set Lst = Get_All_HbShapes(Child, Lst)
        End If
    Next
    Set Get_All_HbShapes = Lst
End Function

'ﾙｰﾄで、空ではなく表示されているﾎﾞﾃﾞｨ・形状ｾｯﾄ取得
Private Function Get_LeafItemLst(ByVal Pt As part) As Collection
    Set Get_LeafItemLst = Nothing
    
    Dim Sel As Selection: Set Sel = Pt.Parent.Selection
    Dim TmpLst As Collection: Set TmpLst = New Collection
    Dim i As Long

    Dim Filter As String
    Filter = "(CATPrtSearch.BodyFeature.Visibility=Shown " & _
            "+ CATPrtSearch.OpenBodyFeature.Visibility=Shown" & _
            "+ CATPrtSearch.MMOrderedGeometricalSet.Visibility=Shown),sel"
    
    CATIA.HSOSynchronized = False
    
    With Sel
        .Clear
        .Add Pt
        .Search Filter
        For i = 1 To .Count2
            TmpLst.Add .Item(i).Value
        Next
        .Clear
    End With
    
    CATIA.HSOSynchronized = True
    
    If TmpLst.Count < 1 Then Exit Function
    
    Dim LeafHBdys As Object: Set LeafHBdys = KCL.InitDic()
    Dim Hbdy As AnyObject 'HybridBody & OrderedGeometricalSets
    For Each Hbdy In Pt.hybridBodies
        LeafHBdys.Add Hbdy, 0
    Next
    For Each Hbdy In Pt.OrderedGeometricalSets
        LeafHBdys.Add Hbdy, 0
    Next
    
    
    Dim Itm As AnyObject
    Dim Lst As Collection: Set Lst = New Collection
    For Each Itm In TmpLst
        Select Case TypeName(Itm)
            Case "Body"
                If Is_LeafBody(Itm) Then Lst.Add Itm
            Case Else 'HybridBody & OrderedGeometricalSets
                If Is_LeafHybridBody(Itm, LeafHBdys) Then Lst.Add Itm
        End Select
    Next
    If Lst.Count < 1 Then Exit Function
    
    Set Get_LeafItemLst = Lst
End Function

'ﾙｰﾄのﾎﾞﾃﾞｨで中身が有るか?
Private Function Is_LeafBody(ByVal Bdy As Body) As Boolean
    Is_LeafBody = Bdy.InBooleanOperation = False And Bdy.Shapes.Count > 0
End Function

'ﾙｰﾄの形状ｾｯﾄで中身が有り可視か?As HybridBody
'prm:Hbdy - HybridBody & OrderedGeometricalSets
Private Function Is_LeafHybridBody(ByVal Hbdy As AnyObject, _
                                   ByVal Dic As Object) As Boolean
    Is_LeafHybridBody = False
    If Not Dic.Exists(Hbdy) Then Exit Function
    
    CATIA.HSOSynchronized = False
    
    Dim Sel As Selection
    Set Sel = KCL.GetParent_Of_T(Hbdy, "PartDocument").Selection
    
    Dim Cnt As Long
    
    With Sel
        .Clear
        .Add Hbdy
        .Search "Visibility=Shown,sel"
        Cnt = .Count2
        .Clear
    End With
    
    CATIA.HSOSynchronized = True
    
    If Cnt > 1 Then Is_LeafHybridBody = True
End Function

'Part新作
Private Function Init_Part(ByVal Prods As Variant, _
                           ByVal PtNum As String) As PartDocument
    Dim Prod As Product
    On Error Resume Next
        Set Prod = Prods.AddNewComponent("Part", PtNum)
    On Error GoTo 0
    Set Init_Part = Prods.Item(Prods.Count).ReferenceProduct.Parent
End Function

'*** camera ***
'表示のUpdate
Private Sub UpdateScene(ByVal Scene As Variant)
    Dim Viewer As Viewer3D: Set Viewer = CATIA.ActiveWindow.ActiveViewer
    Dim VPnt3D As Variant 'Viewpoint3D '
    Set VPnt3D = Viewer.Viewpoint3D
    
    Dim ary As Variant
    ary = GetRangeAry(Scene, 0, 2)
    Call VPnt3D.PutOrigin(ary)
    
    ary = GetRangeAry(Scene, 3, 5)
    Call VPnt3D.PutSightDirection(ary)
    
    ary = GetRangeAry(Scene, 6, 8)
    Call VPnt3D.PutUpDirection(ary)
    
    VPnt3D.FieldOfView = Scene(9)
    VPnt3D.FocusDistance = Scene(10)
    
    Call Viewer.Update
End Sub

'Viewpoint3Dからｼｰﾝ取得
Private Function GetScene3D(ViewPnt3D As Viewpoint3D) As Variant
    Dim vp As Variant: Set vp = ViewPnt3D
    
    Dim origin(2) As Variant: Call vp.GetOrigin(origin)
    
    Dim sight(2) As Variant: Call vp.GetSightDirection(sight)
    GetScene3D = KCL.JoinAry(origin, sight)
    
    Dim up(2) As Variant: Call vp.GetUpDirection(up)
    GetScene3D = KCL.JoinAry(GetScene3D, up)
    
    Dim FieldOfView(0) As Variant: FieldOfView(0) = vp.FieldOfView
    GetScene3D = KCL.JoinAry(GetScene3D, FieldOfView)
    
    Dim FocusDist(0) As Variant: FocusDist(0) = vp.FocusDistance
    GetScene3D = KCL.JoinAry(GetScene3D, FocusDist)
End Function

'現状の視点取得
Private Function GetViewPnt3D() As Viewpoint3D
    Set GetViewPnt3D = CATIA.ActiveWindow.ActiveViewer.Viewpoint3D
End Function

Attribute VB_Name = "sample_ReOrder_Product"
'vba sample_ReOrder_Product ver0.0.1  using-'KCL0.0.12'  by Kantoku
'ｲﾝｽﾀﾝｽ名でのｿｰﾄ順にTreeを並び替えます

'{GP:11}
'{Caption:ﾘｵｰﾀﾞｰ}
'{ControlTipText:ｲﾝｽﾀﾝｽ名でのｿｰﾄ順にTreeを並び替えます}
'{BackColor:16744703}

Option Explicit

Sub CATMain()
    'ﾄﾞｷｭﾒﾝﾄのﾁｪｯｸ
    If Not CanExecute("ProductDocument") Then Exit Sub
    
    'Doc取得
    Dim ProDoc As ProductDocument: Set ProDoc = CATIA.ActiveDocument
    Dim Pros As Products: Set Pros = ProDoc.Product.Products
    If Pros.Count < 2 Then Exit Sub
    
    'ｵﾌﾟｼｮﾝ変更
    Dim AssyMode As AsmConstraintSettingAtt
    Set AssyMode = CATIA.SettingControllers.Item("CATAsmConstraintSettingCtrl")
    Dim OriginalMode As CatAsmPasteComponentMode
    OriginalMode = AssyMode.PasteComponentMode
    
    'ｵﾌﾟｼｮﾝ切り替え
    AssyMode.PasteComponentMode = catPasteWithCstOnCopyAndCut
    
    'ｿｰﾄ済み名前ﾘｽﾄ
    Dim Names: Set Names = Get_SortedNames(Pros)
    
    'ｶｯﾄ
    Dim Sel As Selection: Set Sel = ProDoc.Selection
    Dim Itm As Variant
    
    CATIA.HSOSynchronized = False
    
    Sel.Clear
    For Each Itm In Names
        Sel.Add Pros.Item(Itm)
    Next
    Sel.Cut
    
    'ﾍﾟｰｽﾄ
    With Sel
        .Clear
        .Add Pros
        .Paste
        .Clear
    End With
    
    CATIA.HSOSynchronized = True
    
    'ｵﾌﾟｼｮﾝ戻し,UpDate
    AssyMode.PasteComponentMode = OriginalMode
    ProDoc.Product.Update
End Sub

'ｲﾝｽﾀﾝｽ名でｿｰﾄ済みの名前ﾘｽﾄ
Private Function Get_SortedNames(ByVal Pros As Products) As Object
    Dim Lst As Object
    Set Lst = KCL.InitLst()
    
    Dim Pro As Product
    For Each Pro In Pros
        Lst.Add Pro.Name
    Next
    
    Lst.Sort
    
    Set Get_SortedNames = Lst
End Function
